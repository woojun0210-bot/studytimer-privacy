;;; ------------------------------------------------------------------
;;; AL_FTE.lsp - 문자 찾기/바꾸기 (대화상자)
;;;   ALFTE / ALFIND / ALFR
;;;
;;;   결과 레코드: (종류 엔티티 부가정보 문자)
;;;     종류     : TEXT MTEXT ATTRIB ATTDEF DIM MLEADER TABLE BLOCK
;;;     부가정보 : ATTRIB/BLOCK 은 소유 블록(INSERT), TABLE 은 (행 열)
;;;     문자     : 서식 없는 내용, 여러 줄은 "\n" 으로 연결
;;; ------------------------------------------------------------------

(setq al:*fte-defaults*
  '(("scope" . "1") ("fwhole" . "0") ("fmulti" . "0") ("fcase" . "0")
    ("rwhole" . "0") ("rcase" . "0") ("rdelim" . ",")
    ("t_text" . "1") ("t_mtext" . "1") ("t_attr" . "1") ("t_block" . "1")
    ("t_dim" . "1") ("t_mlead" . "1") ("t_table" . "1")
    ("oneblock" . "0") ("fspace" . "0") ("rspace" . "0") ("foff" . "0") ("roff" . "0")
    ("wild" . "0") ("zoom" . "15") ("rect" . "1")
    ("proc" . "p0") ("ph" . "0") ("phv" . "2.5") ("pw" . "0") ("pwv" . "1.0")
    ("pc" . "0") ("pcv" . "1") ("ps" . "0") ("psv" . "") ("pl" . "0") ("plv" . "")))

(setq al:*fte-main-toggles* '("fwhole" "fmulti" "fcase" "rwhole" "rcase"))
(setq al:*fte-set-toggles*
  '("t_text" "t_mtext" "t_attr" "t_block" "t_dim" "t_mlead" "t_table"
    "oneblock" "fspace" "rspace" "foff" "roff" "wild" "rect" "ph" "pw" "pc" "ps" "pl"))

(setq al:*fte-scopes* '("전체 도면 (모형+배치)" "현재 공간" "모형" "배치" "객체 선택"))

(setq al:*fte-kind-names*
  '(("TEXT" . "문자") ("MTEXT" . "여러줄") ("ATTRIB" . "속성") ("ATTDEF" . "속성정의")
    ("DIM" . "치수") ("MLEADER" . "지시선") ("TABLE" . "표") ("BLOCK" . "블록내부")))

(defun al:fo (k) (al:cfg-get (strcat "FTE_" k) (cdr (assoc k al:*fte-defaults*))))
(defun al:fo-set (k v) (al:cfg-set (strcat "FTE_" k) v))
(defun al:fob (k) (= (al:fo k) "1"))

(defun al:mt-lines (s) (al:str-join (al:mt-paragraphs s) "\n"))
(defun al:lines->mt (s) (al:str-join (mapcar 'al:mt-escape (al:str-split s "\n")) "\\P"))

;;; --- 저장 폴더 (찾기/바꾸기 목록) -----------------------------------

(defun al:data-dir (/ d)
  (setq d (al:catch 'getenv (list "APPDATA")))
  (if (or (null d) (= d "")) (setq d (getvar "TEMPPREFIX")))
  (setq d (strcat (vl-string-right-trim "\\/" d) "\\AutoLisp"))
  (vl-mkdir d)
  (setq d (strcat d "\\FTE"))
  (vl-mkdir d)
  (strcat d "\\")
)

;;; --- 검색 대상 수집 -------------------------------------------------

(defun al:fte-types (/ l)
  (if (al:fob "t_text") (setq l (cons "TEXT" l)))
  (if (al:fob "t_mtext") (setq l (cons "MTEXT" l)))
  (if (or (al:fob "t_attr") (al:fob "t_block")) (setq l (cons "INSERT" l)))
  (if (al:fob "t_attr") (setq l (cons "ATTDEF" l)))
  (if (al:fob "t_dim") (setq l (cons "DIMENSION" l)))
  (if (al:fob "t_mlead") (setq l (cons "MULTILEADER" l)))
  (if (al:fob "t_table") (setq l (cons "ACAD_TABLE" l)))
  (al:str-join l ",")
)

(defun al:fte-ents (/ types scope flt ss)
  (setq types (al:fte-types) scope (al:fo "scope"))
  (if (/= types "")
    (progn
      (setq flt (list (cons 0 types)))
      (setq ss (cond
                 ((= scope "0") (ssget "X" flt))
                 ((= scope "1") (ssget "X" (append flt (list (cons 410 (getvar "CTAB"))))))
                 ((= scope "2") (ssget "X" (append flt '((410 . "Model")))))
                 ((= scope "3") (ssget "X" (append flt '((-4 . "<NOT") (410 . "Model") (-4 . "NOT>")))))
                 (T al:*fte-ss*)))
      (vl-remove-if-not
        '(lambda (e) (and (entget e) (wcmatch (cdr (assoc 0 (entget e))) types)))
        (al:ss->list ss))
    )
  )
)

(defun al:off-layers (/ r l)
  (setq r (tblnext "LAYER" T))
  (while r
    (if (or (< (cdr (assoc 62 r)) 0) (= 1 (logand 1 (cdr (assoc 70 r)))))
      (setq l (cons (strcase (cdr (assoc 2 r))) l))
    )
    (setq r (tblnext "LAYER"))
  )
  l
)

(defun al:fte-off-p (e offl)
  (and offl (member (strcase (cdr (assoc 8 (entget e)))) offl))
)

;; ActiveX 로 문자 읽기/쓰기 (다중 지시선, 표)
(defun al:fte-ax-get (e cell / o)
  (if (al:activex-p)
    (progn
      (setq o (vlax-ename->vla-object e))
      (if cell
        (al:catch 'vla-GetText (list o (car cell) (cadr cell)))
        (al:catch 'vla-get-TextString (list o))
      )
    )
  )
)

(defun al:fte-ax-set (e cell s / o)
  (if (al:activex-p)
    (progn
      (setq o (vlax-ename->vla-object e))
      (not (vl-catch-all-error-p
             (if cell
               (vl-catch-all-apply 'vla-SetText (list o (car cell) (cadr cell) s))
               (vl-catch-all-apply 'vla-put-TextString (list o s)))))
    )
  )
)

(defun al:fte-table-cells (e / o nr nc r c s out)
  (if (al:activex-p)
    (progn
      (setq o (vlax-ename->vla-object e)
            nr (al:catch 'vla-get-Rows (list o))
            nc (al:catch 'vla-get-Columns (list o))
            r 0)
      (if (and nr nc)
        (repeat nr
          (setq c 0)
          (repeat nc
            (setq s (al:catch 'vla-GetText (list o r c)))
            (if (and s (/= s ""))
              (setq out (cons (list "TABLE" e (list r c) (al:mt-lines s)) out))
            )
            (setq c (1+ c))
          )
          (setq r (1+ r))
        )
      )
    )
  )
  (reverse out)
)

;; 블록 정의 안의 문자: ((엔티티 문자) ...)  중첩 블록 4단계까지
(defun al:fte-block-texts (name depth / c b e ed typ out)
  (if (setq c (assoc name al:*fte-blkcache*))
    (cdr c)
    (progn
      (setq b (tblsearch "BLOCK" name))
      (if (and b (= 0 (logand 4 (cdr (assoc 70 b)))))
        (progn
          (setq e (cdr (assoc -2 b)))
          (while e
            (setq ed (entget e) typ (cdr (assoc 0 ed)))
            (if (not (al:fte-off-p e al:*fte-offl*))
              (cond
                ((= typ "TEXT") (setq out (cons (list e (cdr (assoc 1 ed))) out)))
                ((= typ "MTEXT") (setq out (cons (list e (al:mt-lines (al:mtext-string ed))) out)))
                ((and (= typ "DIMENSION") (/= (cdr (assoc 1 ed)) ""))
                 (setq out (cons (list e (cdr (assoc 1 ed))) out)))
                ((and (= typ "INSERT") (< depth 4))
                 (setq out (append (reverse (al:fte-block-texts (cdr (assoc 2 ed)) (1+ depth))) out)))
              )
            )
            (setq e (entnext e))
          )
        )
      )
      (setq out (reverse out)
            al:*fte-blkcache* (cons (cons name out) al:*fte-blkcache*))
      out
    )
  )
)

;; 검색 대상 레코드 목록
(defun al:fte-cands (offl / out ed typ s a)
  (setq al:*fte-blkcache* nil al:*fte-offl* offl)
  (foreach e (al:fte-ents)
    (setq ed (entget e) typ (cdr (assoc 0 ed)))
    (if (not (al:fte-off-p e offl))
      (cond
        ((= typ "TEXT") (setq out (cons (list "TEXT" e nil (cdr (assoc 1 ed))) out)))
        ((= typ "ATTDEF") (setq out (cons (list "ATTDEF" e nil (cdr (assoc 1 ed))) out)))
        ((= typ "MTEXT") (setq out (cons (list "MTEXT" e nil (al:mt-lines (al:mtext-string ed))) out)))
        ((= typ "DIMENSION")
         (if (/= (cdr (assoc 1 ed)) "") (setq out (cons (list "DIM" e nil (cdr (assoc 1 ed))) out))))
        ((= typ "MULTILEADER")
         (if (setq s (al:fte-ax-get e nil)) (setq out (cons (list "MLEADER" e nil (al:mt-lines s)) out))))
        ((= typ "ACAD_TABLE")
         (setq out (append (reverse (al:fte-table-cells e)) out)))
        ((= typ "INSERT")
         (if (and (al:fob "t_attr") (= (cdr (assoc 66 ed)) 1))
           (progn
             (setq a (entnext e))
             (while (and a (= (cdr (assoc 0 (entget a))) "ATTRIB"))
               (if (not (al:fte-off-p a offl))
                 (setq out (cons (list "ATTRIB" a e (cdr (assoc 1 (entget a)))) out))
               )
               (setq a (entnext a))
             )
           )
         )
         (if (al:fob "t_block")
           (foreach x (al:fte-block-texts (cdr (assoc 2 ed)) 0)
             (setq out (cons (list "BLOCK" (car x) e (cadr x)) out))
           )
         ))
      )
    )
  )
  (reverse out)
)

;;; --- 찾기 -----------------------------------------------------------

(defun al:fte-prep (s sp cs)
  (if sp (setq s (al:remove-spaces s)))
  (if cs s (strcase s))
)

(defun al:fte-do-find (text / cs sp terms cps res seen ms)
  (setq cs (al:fob "fcase") sp (al:fob "fspace"))
  (setq terms (if (al:fob "fmulti")
                (vl-remove "" (mapcar 'al:str-trim (al:str-split text ",")))
                (list text)))
  (setq cps (mapcar '(lambda (x) (al:pm-compile (if sp (al:remove-spaces x) x) (al:fob "wild") (al:fob "fwhole") cs))
                    terms))
  (foreach c (al:fte-cands (if (al:fob "foff") (al:off-layers)))
    (setq ms (al:fte-prep (nth 3 c) sp cs))
    (if (and (vl-some '(lambda (cp) (al:pm-find cp ms 1)) cps)
             (not (and (al:fob "oneblock") (= (car c) "BLOCK") (member (cadr c) seen))))
      (progn
        (if (= (car c) "BLOCK") (setq seen (cons (cadr c) seen)))
        (setq res (cons c res))
      )
    )
  )
  (reverse res)
)

;;; --- 바꾸기 ---------------------------------------------------------

;; cps: ((패턴 바꿀문자 대소문자 원래찾을문자) ...)
(defun al:fte-apply-pairs (s cps sp / total r base)
  (setq total 0)
  (foreach p cps
    (setq base (if sp (al:remove-spaces s) s)
          r (al:pm-replace (car p) base (cadr p) (caddr p)))
    (if (> (cadr r) 0) (setq s (car r) total (+ total (cadr r))))
  )
  (list s total)
)

;; 서식을 유지한 채 바꾸기 (와일드카드/전체일치/띄어쓰기무시/제외 없을 때)
(defun al:fte-raw-replace (raw cps / total r)
  (setq total 0)
  (foreach p cps
    (setq r (al:str-replace raw (cadddr p) (cadr p) (caddr p) T))
    (if (> (cadr r) 0) (setq raw (car r) total (+ total (cadr r))))
  )
  (list raw total)
)

(defun al:fte-entmod-1 (e s / ed)
  (setq ed (entget e))
  (entmod (subst (cons 1 s) (assoc 1 ed) ed))
)

;; 한 레코드 바꾸기. 반환 (바꾼개수 새문자) 또는 nil
(defun al:fte-replace-cand (c cps simple sp / kind e typ raw r ok)
  (setq kind (car c) e (cadr c)
        typ (if (= kind "BLOCK") (cdr (assoc 0 (entget e))) kind))
  (if (member typ '("MTEXT" "MLEADER" "TABLE"))
    (progn
      (setq raw (cond ((= typ "MTEXT") (al:mtext-string (entget e)))
                      ((= typ "MLEADER") (al:fte-ax-get e nil))
                      (T (al:fte-ax-get e (caddr c)))))
      (if raw
        (if simple
          (setq r (al:fte-raw-replace raw cps))
          (progn
            (setq r (al:fte-apply-pairs (al:mt-lines raw) cps sp))
            (if (> (cadr r) 0) (setq r (list (al:lines->mt (car r)) (cadr r))))
          )
        )
      )
    )
    (setq r (al:fte-apply-pairs (nth 3 c) cps sp))
  )
  (if (and r (> (cadr r) 0))
    (progn
      (al:unlock-for e (caddr c))
      (setq ok (cond
                 ((= typ "MTEXT") (entmod (al:mtext-set (entget e) (car r))))
                 ((= typ "MLEADER") (al:fte-ax-set e nil (car r)))
                 ((= typ "TABLE") (al:fte-ax-set e (caddr c) (car r)))
                 (T (al:fte-entmod-1 e (car r)))))
      (if ok
        (list (cadr r) (if (member typ '("MTEXT" "MLEADER" "TABLE")) (al:mt-lines (car r)) (car r)))
        (progn (setq al:*fail* (1+ al:*fail*)) nil)
      )
    )
  )
)

(defun al:fte-do-replace (/ cs sp wild whole cps simple done res r n cnt regen owners)
  (setq cs (al:fob "rcase") sp (al:fob "rspace") wild (al:fob "wild") whole (al:fob "rwhole"))
  (setq cps (mapcar '(lambda (p)
                       (list (al:pm-compile (if sp (al:remove-spaces (car p)) (car p)) wild whole cs)
                             (cadr p) cs (car p)))
                    al:*fte-pairs*))
  (setq simple (and (not wild) (not whole) (not sp)
                    (not (vl-some '(lambda (p) (cadr (car p))) cps))))
  (setq al:*fail* 0 n 0 cnt 0)
  (foreach c (al:fte-cands (if (al:fob "roff") (al:off-layers)))
    (if (not (and (= (car c) "BLOCK") (member (cadr c) done)))
      (if (setq r (al:fte-replace-cand c cps simple sp))
        (progn
          (setq n (1+ n) cnt (+ cnt (car r))
                res (cons (list (car c) (cadr c) (caddr c) (cadr r)) res))
          (if (= (car c) "BLOCK") (setq done (cons (cadr c) done) regen T))
          (if (= (car c) "ATTRIB") (setq owners (cons (caddr c) owners)))
        )
      )
    )
  )
  (foreach o owners (entupd o))
  (if regen (command "_.REGEN"))
  (al:layer-relock)
  (setq al:*fte-status*
         (strcat "바꾸기 완료: 객체 " (itoa n) "개, " (itoa cnt) "곳"
                 (if (> al:*fail* 0) (strcat " / 바꾸지 못한 객체 " (itoa al:*fail*) "개") "")))
  (reverse res)
)

;;; --- 찾은 문자 처리 (삭제 / 특성 변경) ------------------------------

(defun al:set-dxf (ed code val)
  (if (assoc code ed)
    (subst (cons code val) (assoc code ed) ed)
    (append ed (list (cons code val)))
  )
)

(defun al:fte-change-props (c / e ed typ)
  (setq e (cadr c) ed (entget e) typ (cdr (assoc 0 ed)))
  (if (member typ '("TEXT" "MTEXT" "ATTRIB" "ATTDEF"))
    (progn
      (al:unlock-for e (caddr c))
      (if (and (al:fob "ph") (> (atof (al:fo "phv")) 0.0)) (setq ed (al:set-dxf ed 40 (atof (al:fo "phv")))))
      (if (and (al:fob "pw") (/= typ "MTEXT") (> (atof (al:fo "pwv")) 0.0)) (setq ed (al:set-dxf ed 41 (atof (al:fo "pwv")))))
      (if (and (al:fob "ps") (tblsearch "STYLE" (al:fo "psv"))) (setq ed (al:set-dxf ed 7 (al:fo "psv"))))
      (if (al:fob "pc") (setq ed (al:set-dxf ed 62 (max 0 (min 256 (atoi (al:fo "pcv")))))))
      (if (and (al:fob "pl") (tblsearch "LAYER" (al:fo "plv"))) (setq ed (al:set-dxf ed 8 (al:fo "plv"))))
      (if (entmod ed)
        (progn (if (= (type (caddr c)) 'ENAME) (entupd (caddr c))) T)
      )
    )
  )
)

;; 반환: 처리 후 남은 결과 목록
(defun al:fte-process (res / p n keep regen)
  (setq p (al:fo "proc") n 0)
  (cond
    ((= p "p1")
     (foreach c res
       (if (and (member (car c) '("TEXT" "MTEXT")) (progn (al:unlock-for (cadr c) nil) (entdel (cadr c))))
         (setq n (1+ n))
         (setq keep (cons c keep))
       )
     )
     (al:layer-relock)
     (setq al:*fte-status* (strcat (cond (al:*fte-status*) ("")) " / 찾은 문자 " (itoa n) "개 삭제"))
     (reverse keep))
    ((= p "p2")
     (foreach c res
       (if (al:fte-change-props c)
         (progn (setq n (1+ n)) (if (= (car c) "BLOCK") (setq regen T)))
       )
     )
     (if regen (command "_.REGEN"))
     (al:layer-relock)
     (setq al:*fte-status* (strcat (cond (al:*fte-status*) ("")) " / 특성 변경 " (itoa n) "개"))
     res)
    (T res)
  )
)

;;; --- 위치, 확대, 선택 -----------------------------------------------

(defun al:fte-target (c)
  (if (member (car c) '("ATTRIB" "BLOCK")) (caddr c) (cadr c))
)

;; 블록 내부 문자의 WCS 위치 (1단계 변환)
(defun al:fte-inner-pt (inner ins / ied ed bp p sx sy)
  (setq ied (entget inner) ed (entget ins)
        bp (cdr (assoc 10 (tblsearch "BLOCK" (cdr (assoc 2 ed)))))
        p (cdr (assoc 10 ied))
        sx (cond ((cdr (assoc 41 ed))) (1.0))
        sy (cond ((cdr (assoc 42 ed))) (1.0)))
  (al:v+ (cdr (assoc 10 ed))
         (al:rot (list (* sx (- (car p) (car bp))) (* sy (- (cadr p) (cadr bp))))
                 (cdr (assoc 50 ed))))
)

;; 결과의 영역: ((최소점) (최대점))
(defun al:fte-extent (c / e bb p h ed sy)
  (setq e (cadr c))
  (cond
    ((= (car c) "BLOCK")
     (setq ed (entget (caddr c))
           sy (abs (cond ((cdr (assoc 42 ed))) (1.0)))
           h (* sy (cond ((cdr (assoc 40 (entget e)))) (1.0)))
           p (al:fte-inner-pt e (caddr c)))
     (list p (al:v+ p (list (* h 0.8 (max 1 (strlen (nth 3 c)))) h))))
    ((setq bb (al:bbox e)) bb)
    (T
     (setq p (cdr (assoc 10 (entget e))) h (cond ((cdr (assoc 40 (entget e)))) (1.0)))
     (list p (al:v+ p (list (* h 0.8 (max 1 (strlen (nth 3 c)))) h))))
  )
)

(defun al:fte-height (c / ed)
  (setq ed (entget (cadr c)))
  (cond ((cdr (assoc 40 ed))) (1.0))
)

(defun al:grbox (p1 p2)
  (grdraw p1 (list (car p2) (cadr p1)) 1 1)
  (grdraw (list (car p2) (cadr p1)) p2 1 1)
  (grdraw p2 (list (car p1) (cadr p2)) 1 1)
  (grdraw (list (car p1) (cadr p2)) p1 1 1)
)

(defun al:fte-zoom (c / tgt lay ex h)
  (setq tgt (al:fte-target c)
        lay (cdr (assoc 410 (entget tgt))))
  (if (and lay (/= (strcase lay) (strcase (getvar "CTAB"))))
    (setvar "CTAB" lay)
  )
  (setq ex (al:fte-extent c)
        h (max (al:fte-height c) (- (cadr (cadr ex)) (cadr (car ex)))))
  (command "_.ZOOM" "_C" (al:p3 (al:mid (car ex) (cadr ex))) (* h (max 1.0 (atof (al:fo "zoom")))))
  (if (al:fob "rect") (al:grbox (car ex) (cadr ex)))
)

(defun al:fte-in-ctab (c / lay)
  (setq lay (cdr (assoc 410 (entget (al:fte-target c)))))
  (or (null lay) (= (strcase lay) (strcase (getvar "CTAB"))))
)

(defun al:fte-select (lst / out)
  (foreach c lst
    (if (and (entget (al:fte-target c)) (al:fte-in-ctab c) (not (member (al:fte-target c) out)))
      (setq out (cons (al:fte-target c) out))
    )
  )
  (reverse out)
)

;;; --- 바꾸기 목록 (텍스트 파일, 엑셀, 저장 목록) ---------------------

(defun al:fte-read-pairs (fname delim / f ln p out)
  (if (setq f (open fname "r"))
    (progn
      (while (setq ln (read-line f))
        (if (setq p (vl-string-search delim ln))
          (setq out (cons (list (substr ln 1 p) (substr ln (+ p 1 (strlen delim)))) out))
        )
      )
      (close f)
    )
  )
  (reverse out)
)

(defun al:var->str (v)
  (if (= (type v) 'VARIANT) (setq v (vlax-variant-value v)))
  (cond
    ((null v) "")
    ((= (type v) 'STR) v)
    ((numberp v) (al:num->str v))
    (T "")
  )
)

(defun al:fte-from-excel (/ xl rng v rows out)
  (setq xl (al:catch 'vlax-get-object (list "Excel.Application")))
  (if (null xl)
    (progn (alert "실행 중인 엑셀이 없습니다.\n엑셀 파일을 먼저 여세요.") nil)
    (progn
      (princ "\n엑셀에서 [찾을 문자 | 바꿀 문자] 두 열을 선택한 뒤 CAD 로 돌아와 Enter: ")
      (getstring)
      (setq rng (al:catch 'vlax-get-property (list xl 'Selection))
            v (if rng (al:catch 'vlax-get-property (list rng 'Value2))))
      (if (and v (= (type (vlax-variant-value v)) 'SAFEARRAY))
        (progn
          (setq rows (vlax-safearray->list (vlax-variant-value v)))
          (foreach r rows
            (if (and (>= (length r) 2) (/= (al:var->str (car r)) ""))
              (setq out (cons (list (al:var->str (car r)) (al:var->str (cadr r))) out))
            )
          )
        )
        (alert "엑셀에서 두 열 이상을 선택해야 합니다.")
      )
      (if rng (vlax-release-object rng))
      (vlax-release-object xl)
      (reverse out)
    )
  )
)

(defun al:fte-saved-names ()
  (mapcar '(lambda (f) (substr f 4 (- (strlen f) 7)))
          (vl-sort (vl-directory-files (al:data-dir) "FR_*.txt" 1) '<))
)

(defun al:fte-save-list (name / f)
  (if (setq f (open (strcat (al:data-dir) "FR_" name ".txt") "w"))
    (progn
      (foreach p al:*fte-pairs* (write-line (strcat (car p) "\t" (cadr p)) f))
      (close f)
      T
    )
  )
)

;;; --- 대화상자 -------------------------------------------------------

(defun al:dcl-file (/ fn f)
  (if (and al:*dcl-path* (findfile al:*dcl-path*))
    al:*dcl-path*
    (progn
      (setq fn (vl-filename-mktemp "al_fte.dcl"))
      (if (setq f (open fn "w"))
        (progn
          (foreach l al:*dcl-fte* (write-line l f))
          (close f)
          (setq al:*dcl-path* fn)
        )
      )
    )
  )
)

(defun al:fill-list (key items)
  (start_list key)
  (mapcar 'add_list items)
  (end_list)
)

(defun al:fte-short (s / n)
  (setq s (car (al:str-replace s "\n" " " T nil)))
  (if (> (strlen s) 60)
    (strcat (substr s 1 (al:safe-cut s 60)) "...")
    s
  )
)

(defun al:fte-row (i c / lay)
  (setq lay (if (entget (al:fte-target c)) (cdr (assoc 8 (entget (al:fte-target c)))) ""))
  (strcat (itoa i) "\t" (cdr (assoc (car c) al:*fte-kind-names*)) "\t" lay "\t" (al:fte-short (nth 3 c)))
)

(defun al:fte-fill-results (/ i)
  (setq i 0)
  (al:fill-list "results" (mapcar '(lambda (c) (al:fte-row (setq i (1+ i)) c)) al:*fte-results*))
  (if al:*fte-rsel* (set_tile "results" al:*fte-rsel*))
  (set_tile "status" (cond (al:*fte-status*) ("")))
)

(defun al:fte-fill-pairs ()
  (al:fill-list "rlist" (mapcar '(lambda (p) (strcat (car p) "\t→ " (cadr p))) al:*fte-pairs*))
)

(defun al:fte-fill-saved (/ names)
  (setq al:*fte-saved* (al:fte-saved-names))
  (al:fill-list "rsaved" al:*fte-saved*)
)

(defun al:fte-history () (vl-remove "" (al:str-split (al:cfg-get "FTE_hist" "") (chr 31))))

(defun al:fte-history-add (s / h)
  (setq h (cons s (vl-remove s (al:fte-history))))
  (if (> (length h) 15) (setq h (reverse (cdr (reverse h)))))
  (al:cfg-set "FTE_hist" (al:str-join h (chr 31)))
)

(defun al:fte-procinfo ()
  (cond
    ((= (al:fo "proc") "p1") "※ 찾은 문자 처리: 삭제 (검색 설정에서 변경)")
    ((= (al:fo "proc") "p2") "※ 찾은 문자 처리: 특성 변경 (검색 설정에서 변경)")
    (T "")
  )
)

(defun al:sel-indices (str)
  (if (and str (/= str "")) (mapcar 'atoi (al:str-split (al:str-trim str) " ")))
)

(defun al:remove-indices (lst idx / i out)
  (setq i 0)
  (foreach x lst
    (if (not (member i idx)) (setq out (cons x out)))
    (setq i (1+ i))
  )
  (reverse out)
)

;; 대화상자 값을 전역/설정에 보관
(defun al:fte-keep-tiles ()
  (al:fo-set "scope" (get_tile "scope"))
  (foreach k al:*fte-main-toggles* (al:fo-set k (get_tile k)))
  (al:fo-set "rdelim" (get_tile "rdelim"))
  (setq al:*fte-ftext* (get_tile "ftext")
        al:*fte-rfind* (get_tile "rfind")
        al:*fte-rrepl* (get_tile "rrepl")
        al:*fte-rsname* (get_tile "rsname")
        al:*fte-rsel* (get_tile "results"))
)

(defun al:fte-close (code)
  (al:fte-keep-tiles)
  (setq al:*fte-pos* (done_dialog code))
)

(defun al:fte-init ()
  (al:fill-list "scope" al:*fte-scopes*)
  (set_tile "scope" (al:fo "scope"))
  (mode_tile "selobj" (if (= (al:fo "scope") "4") 0 1))
  (foreach k al:*fte-main-toggles* (set_tile k (al:fo k)))
  (set_tile "rdelim" (al:fo "rdelim"))
  (set_tile "ftext" (cond (al:*fte-ftext*) ("")))
  (set_tile "rfind" (cond (al:*fte-rfind*) ("")))
  (set_tile "rrepl" (cond (al:*fte-rrepl*) ("")))
  (set_tile "rsname" (cond (al:*fte-rsname*) ("")))
  (al:fill-list "fhist" (al:fte-history))
  (al:fte-fill-pairs)
  (al:fte-fill-saved)
  (al:fte-fill-results)
  (set_tile "procinfo" (al:fte-procinfo))
  (mode_tile "ftext" 2)

  (action_tile "scope" "(mode_tile \"selobj\" (if (= $value \"4\") 0 1))")
  (action_tile "selobj" "(al:fte-close 10)")
  (action_tile "fpick" "(al:fte-close 11)")
  (action_tile "fpickm" "(al:fte-close 12)")
  (action_tile "rpick" "(al:fte-close 13)")
  (action_tile "dofind" "(al:fte-close 14)")
  (action_tile "doreplace" "(al:fte-close 15)")
  (action_tile "rtxt" "(al:fte-close 16)")
  (action_tile "rxls" "(al:fte-close 17)")
  (action_tile "rzoom" "(al:fte-close 20)")
  (action_tile "results" "(if (= $reason 4) (al:fte-close 20))")
  (action_tile "rsel" "(al:fte-close 21)")
  (action_tile "rselall" "(al:fte-close 22)")
  (action_tile "rline" "(al:fte-close 23)")
  (action_tile "rerase" "(al:fte-close 24)")
  (action_tile "rremove" "(al:fte-act-remove)")
  (action_tile "fhist" "(al:fte-act-hist $value)")
  (action_tile "fhclr" "(al:cfg-set \"FTE_hist\" \"\")(al:fill-list \"fhist\" nil)")
  (action_tile "radd" "(al:fte-act-add)")
  (action_tile "rdel" "(al:fte-act-pairdel)")
  (action_tile "rclr" "(setq al:*fte-pairs* nil)(al:fte-fill-pairs)")
  (action_tile "rload" "(al:fte-act-load)")
  (action_tile "rsdel" "(al:fte-act-sdel)")
  (action_tile "rsave" "(al:fte-act-save)")
  (action_tile "settings" "(al:fte-settings)(set_tile \"procinfo\" (al:fte-procinfo))")
  (action_tile "cancel" "(al:fte-close 0)")
)

(defun al:fte-act-hist (v / h)
  (setq h (al:fte-history))
  (if (and v (/= v "")) (set_tile "ftext" (nth (atoi v) h)))
)

(defun al:fte-act-remove ()
  (setq al:*fte-results* (al:remove-indices al:*fte-results* (al:sel-indices (get_tile "results")))
        al:*fte-rsel* nil
        al:*fte-status* (strcat "목록 " (itoa (length al:*fte-results*)) "개"))
  (al:fte-fill-results)
)

(defun al:fte-act-add (/ f r)
  (setq f (get_tile "rfind") r (get_tile "rrepl"))
  (if (= f "")
    (set_tile "status" "찾을 문자를 입력하세요.")
    (progn
      (setq al:*fte-pairs* (append al:*fte-pairs* (list (list f r))))
      (al:fte-fill-pairs)
      (set_tile "rfind" "")
      (set_tile "rrepl" "")
      (mode_tile "rfind" 2)
    )
  )
)

(defun al:fte-act-pairdel ()
  (setq al:*fte-pairs* (al:remove-indices al:*fte-pairs* (al:sel-indices (get_tile "rlist"))))
  (al:fte-fill-pairs)
)

(defun al:fte-act-load (/ v)
  (setq v (get_tile "rsaved"))
  (if (and v (/= v "") al:*fte-saved*)
    (progn
      (setq al:*fte-pairs* (al:fte-read-pairs (strcat (al:data-dir) "FR_" (nth (atoi v) al:*fte-saved*) ".txt") "\t"))
      (al:fte-fill-pairs)
      (set_tile "status" (strcat "목록 불러옴: " (nth (atoi v) al:*fte-saved*)))
    )
  )
)

(defun al:fte-act-sdel (/ v)
  (setq v (get_tile "rsaved"))
  (if (and v (/= v "") al:*fte-saved*)
    (progn
      (vl-file-delete (strcat (al:data-dir) "FR_" (nth (atoi v) al:*fte-saved*) ".txt"))
      (al:fte-fill-saved)
    )
  )
)

(defun al:fte-act-save (/ name)
  (setq name (al:str-trim (get_tile "rsname")))
  (cond
    ((= name "") (set_tile "status" "저장 이름을 입력하세요."))
    ((wcmatch name "*[\\/:`*`?\"<>|]*") (set_tile "status" "이름에 \\ / : * ? \" < > | 는 쓸 수 없습니다."))
    ((null al:*fte-pairs*) (set_tile "status" "저장할 목록이 없습니다."))
    ((and (>= (length (al:fte-saved-names)) 20) (not (member name (al:fte-saved-names))))
     (set_tile "status" "저장 목록은 20개까지입니다. 먼저 하나를 삭제하세요."))
    ((al:fte-save-list name)
     (al:fte-fill-saved)
     (set_tile "status" (strcat "목록 저장: " name)))
    (T (set_tile "status" "저장하지 못했습니다."))
  )
)

;; 검색 설정 (중첩 대화상자)
(defun al:fte-settings (/ styles layers r i)
  (if (new_dialog "al_fte_set" al:*fte-dclid*)
    (progn
      (foreach k al:*fte-set-toggles* (set_tile k (al:fo k)))
      (foreach k '("zoom" "phv" "pwv" "pcv") (set_tile k (al:fo k)))
      (set_tile "proc" (al:fo "proc"))
      (setq r (tblnext "STYLE" T))
      (while r
        (if (/= (cdr (assoc 2 r)) "") (setq styles (cons (cdr (assoc 2 r)) styles)))
        (setq r (tblnext "STYLE"))
      )
      (setq r (tblnext "LAYER" T))
      (while r (setq layers (cons (cdr (assoc 2 r)) layers) r (tblnext "LAYER")))
      (setq styles (vl-sort styles '<) layers (vl-sort layers '<))
      (setq al:*fte-styles* styles al:*fte-layers* layers)
      (al:fill-list "psv" styles)
      (al:fill-list "plv" layers)
      (if (setq i (vl-position (al:fo "psv") styles)) (set_tile "psv" (itoa i)))
      (if (setq i (vl-position (al:fo "plv") layers)) (set_tile "plv" (itoa i)))
      (action_tile "accept" "(if (al:fte-settings-save) (done_dialog 1))")
      (start_dialog)
    )
  )
)

(defun al:fte-settings-save (/ z v)
  (setq z (atof (get_tile "zoom")))
  (if (<= z 0.0)
    (progn (alert "Zoom 단계는 0보다 커야 합니다.") nil)
    (progn
      (foreach k al:*fte-set-toggles* (al:fo-set k (get_tile k)))
      (foreach k '("zoom" "phv" "pwv" "pcv") (al:fo-set k (get_tile k)))
      (al:fo-set "proc" (get_tile "proc"))
      (if (and (setq v (get_tile "psv")) (/= v "")) (al:fo-set "psv" (nth (atoi v) al:*fte-styles*)))
      (if (and (setq v (get_tile "plv")) (/= v "")) (al:fo-set "plv" (nth (atoi v) al:*fte-layers*)))
      T
    )
  )
)

;;; --- 대화상자 밖에서 실행하는 동작 ----------------------------------

(defun al:pick-text-string (/ s e ed typ)
  (if (setq s (nentsel "\n문자 선택: "))
    (progn
      (setq e (car s) ed (entget e) typ (cdr (assoc 0 ed)))
      (cond
        ((= typ "MTEXT") (al:str-join (al:mt-paragraphs (al:mtext-string ed)) " "))
        ((member typ '("TEXT" "ATTRIB" "ATTDEF")) (cdr (assoc 1 ed)))
        (T (princ "\n문자가 아닙니다.") nil)
      )
    )
  )
)

(defun al:fte-sel-results ()
  (mapcar '(lambda (i) (nth i al:*fte-results*)) (al:sel-indices al:*fte-rsel*))
)

;; 반환: 다시 대화상자를 열면 T
(defun al:fte-run (st / s ss l n pt)
  (cond
    ((= st 10)
     (princ "\n검색할 객체 선택: ")
     (if (setq ss (ssget)) (setq al:*fte-ss* ss al:*fte-status* (strcat "객체 " (itoa (sslength ss)) "개 선택됨")))
     T)
    ((= st 11)
     (if (setq s (al:pick-text-string)) (setq al:*fte-ftext* s))
     T)
    ((= st 12)
     (princ "\n찾을 문자들 선택: ")
     (if (setq ss (ssget '((0 . "TEXT,MTEXT"))))
       (progn
         (foreach e (al:ss->list ss)
           (setq s (al:ent-text (entget e)))
           (if (= (cdr (assoc 0 (entget e))) "MTEXT") (setq s (al:mt-plain s)))
           (if (and (/= s "") (not (member s l))) (setq l (cons s l)))
         )
         (setq al:*fte-ftext* (al:str-join (reverse l) ","))
         (al:fo-set "fmulti" "1")
       )
     )
     T)
    ((= st 13)
     (if (setq s (al:pick-text-string)) (setq al:*fte-rfind* s))
     T)
    ((= st 14)
     (cond
       ((= al:*fte-ftext* "") (setq al:*fte-status* "찾을 내용을 입력하세요."))
       ((and (= (al:fo "scope") "4") (null al:*fte-ss*)) (setq al:*fte-status* "검색할 객체를 먼저 선택하세요."))
       (T
        (al:fte-history-add al:*fte-ftext*)
        (setq al:*fte-results* (al:fte-do-find al:*fte-ftext*)
              al:*fte-rsel* nil
              al:*fte-status* (strcat "찾은 문자: " (itoa (length al:*fte-results*)) "개"))
        (if (and al:*fte-results* (/= (al:fo "proc") "p0"))
          (progn
            (setq al:*fte-results* (al:fte-process al:*fte-results*))
            (al:undo-end) (al:undo-begin)
          )
        ))
     )
     T)
    ((= st 15)
     (cond
       ((null al:*fte-pairs*) (setq al:*fte-status* "바꾸기 목록이 비어 있습니다. [목록에 추가]를 누르세요."))
       ((and (= (al:fo "scope") "4") (null al:*fte-ss*)) (setq al:*fte-status* "검색할 객체를 먼저 선택하세요."))
       (T
        (setq al:*fte-results* (al:fte-do-replace) al:*fte-rsel* nil)
        (if (and al:*fte-results* (/= (al:fo "proc") "p0"))
          (setq al:*fte-results* (al:fte-process al:*fte-results*))
        )
        (al:undo-end) (al:undo-begin))
     )
     T)
    ((= st 16)
     (if (setq s (getfiled "찾기/바꾸기 목록 텍스트 파일" (getvar "DWGPREFIX") "txt;csv" 0))
       (progn
         (setq l (al:fte-read-pairs s (if (= (al:fo "rdelim") "") "," (al:fo "rdelim"))))
         (setq al:*fte-pairs* (append al:*fte-pairs* l)
               al:*fte-status* (strcat "텍스트 파일에서 " (itoa (length l)) "개 추가"))
       )
     )
     T)
    ((= st 17)
     (setq l (al:fte-from-excel))
     (setq al:*fte-pairs* (append al:*fte-pairs* l)
           al:*fte-status* (strcat "엑셀에서 " (itoa (length l)) "개 추가"))
     T)
    ((= st 20)
     (setq l (al:fte-sel-results))
     (cond
       ((null l) (setq al:*fte-status* "확대할 항목을 선택하세요.") T)
       ((not (entget (al:fte-target (car l)))) (setq al:*fte-status* "삭제된 객체입니다.") T)
       (T
        (al:fte-zoom (car l))
        (princ "\n확인 후 Enter 를 누르면 대화상자로 돌아갑니다: ")
        (getstring)
        T)
     ))
    ((member st '(21 22))
     (setq l (al:fte-select (if (= st 21) (al:fte-sel-results) al:*fte-results*)))
     (if l
       (progn
         (setq al:*fte-pickfirst* (al:list->ss l))
         (princ (strcat "\n" (itoa (length l)) "개 객체를 선택했습니다. (현재 공간의 객체만)"))
         nil)
       (progn (setq al:*fte-status* "현재 공간에서 선택할 객체가 없습니다.") T)
     ))
    ((= st 23)
     (setq l (vl-remove-if-not 'al:fte-in-ctab (al:fte-sel-results)))
     (if (null l)
       (setq al:*fte-status* "현재 공간의 항목을 선택하세요.")
       (if (setq pt (getpoint "\n연결선 기준점: "))
         (progn
           (foreach c l
             (setq s (al:fte-extent c))
             (al:make-line pt (al:mid (car s) (cadr s)))
           )
           (al:undo-end) (al:undo-begin)
           (setq al:*fte-status* (strcat "연결선 " (itoa (length l)) "개 작성"))
         )
       )
     )
     T)
    ((= st 24)
     (setq l (al:fte-sel-results) n 0)
     (foreach c l
       (if (and (member (car c) '("TEXT" "MTEXT")) (entget (cadr c)))
         (progn
           (al:unlock-for (cadr c) nil)
           (if (entdel (cadr c))
             (setq n (1+ n) al:*fte-results* (vl-remove c al:*fte-results*))
           )
         )
       )
     )
     (al:layer-relock)
     (al:undo-end) (al:undo-begin)
     (setq al:*fte-rsel* nil
           al:*fte-status* (strcat (itoa n) "개 삭제 (TEXT, MTEXT 만 삭제됩니다)"))
     T)
    (T nil)
  )
)

(defun al:fte-dialog (/ dcl again st)
  (setq al:*fte-pickfirst* nil al:*fte-ss* nil al:*fte-status* nil)
  (if (not (setq dcl (al:dcl-file)))
    (princ "\n대화상자 파일을 만들 수 없습니다.")
    (progn
      (setq al:*fte-dclid* (load_dialog dcl) again T)
      (while again
        (if (not (new_dialog "al_fte" al:*fte-dclid* "" (cond (al:*fte-pos*) ('(-1 -1)))))
          (progn (princ "\n대화상자를 열 수 없습니다.") (setq again nil))
          (progn
            (al:fte-init)
            (setq st (start_dialog))
            (setq again (al:fte-run st))
          )
        )
      )
      (unload_dialog al:*fte-dclid*)
    )
  )
)

(defun al:fte-command ()
  (al:begin)
  (al:fte-dialog)
  (al:end)
  (if al:*fte-pickfirst* (sssetfirst nil al:*fte-pickfirst*))
  (princ)
)

(defun c:ALFTE () (al:fte-command))
(defun c:ALFIND () (al:fte-command))
(defun c:ALFR () (al:fte-command))
