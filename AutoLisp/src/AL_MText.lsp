;;; ------------------------------------------------------------------
;;; AL_MText.lsp - 문자 변환
;;;   ALT2M    : TEXT -> MTEXT (여러 줄을 하나로 합치기 / 하나씩 변환)
;;;   ALM2T    : MTEXT -> TEXT (줄마다 TEXT 하나)
;;;   ALMCLEAN : MTEXT 서식(글꼴, 색, 높이 등) 지우기
;;; ------------------------------------------------------------------

;; TEXT 의 왼쪽 위 점 (WCS)
(defun al:text-topleft (ed / tb ang p)
  (setq ang (cdr (assoc 50 ed)) p (cdr (assoc 10 ed)))
  (setq tb (al:catch 'textbox (list ed)))
  (if (null tb) (setq tb (list '(0.0 0.0) (list 0.0 (cdr (assoc 40 ed))))))
  (al:v+ p (al:rot (list (car (car tb)) (cadr (cadr tb))) ang))
)

(defun al:make-mtext (src pt content h ang spacing / chunks ed)
  (setq chunks (al:str-chunks content 250))
  (setq ed (list '(0 . "MTEXT") '(100 . "AcDbEntity") (assoc 8 src)))
  (if (assoc 62 src) (setq ed (append ed (list (assoc 62 src)))))
  (setq ed (append ed (list '(100 . "AcDbMText") (cons 10 (al:p3 pt)) (cons 40 h)
                            '(41 . 0.0) '(71 . 1) '(72 . 1))))
  (foreach c (reverse (cdr (reverse chunks))) (setq ed (append ed (list (cons 3 c)))))
  (setq ed (append ed (list (cons 1 (last chunks)) (assoc 7 src) (cons 50 ang))))
  (if spacing (setq ed (append ed (list '(73 . 2) (cons 44 spacing)))))
  (entmake ed)
)

(defun al:text-content (ed / wf s)
  (setq s (al:mt-escape (cdr (assoc 1 ed))) wf (cdr (assoc 41 ed)))
  (if (and wf (not (equal wf 1.0 1e-6)))
    (strcat "{\\W" (rtos wf 2 3) ";" s "}")
    s
  )
)

(defun c:ALT2M (/ ss lst mode del ed0 ang0 org h items rows content tl ys gap sp n)
  (al:begin)
  (princ "\nMTEXT 로 바꿀 TEXT 선택: ")
  (if (setq ss (ssget '((0 . "TEXT"))))
    (progn
      (setq lst (al:ss->list ss))
      (setq mode (if (> (length lst) 1)
                   (al:kword "\n변환 방식 - 하나로 합치기(M)/각각 변환(E) [Merge/Each] <Merge>: " "Merge Each" "Merge")
                   "Each"))
      (setq del (al:yes-p "\n원본 TEXT 를 삭제할까요" "Yes"))
      (setq n 0)
      (if (= mode "Each")
        (foreach e lst
          (setq ed0 (entget e))
          (if (al:make-mtext ed0 (al:text-topleft ed0) (al:text-content ed0)
                             (cdr (assoc 40 ed0)) (cdr (assoc 50 ed0)) nil)
            (progn (setq n (1+ n)) (if del (entdel e)))
          )
        )
        (progn
          ;; 첫 문자의 회전 방향을 기준 좌표계로 사용
          (setq ed0 (entget (car lst))
                ang0 (cdr (assoc 50 ed0))
                h (cdr (assoc 40 ed0))
                org (al:text-topleft ed0))
          (setq items (mapcar '(lambda (e / ed)
                                 (setq ed (entget e))
                                 (cons (al:rot (al:v- (al:text-topleft ed) org) (- ang0)) ed))
                              lst))
          (setq rows (al:group-rows items (* h 0.5)))
          (setq content
                 (al:str-join
                   (mapcar '(lambda (r) (al:str-join (mapcar '(lambda (it) (al:text-content (cdr it))) r) " "))
                           rows)
                   "\\P"))
          ;; 왼쪽 위 기준점
          (setq tl (list (apply 'min (mapcar 'caar items)) (apply 'max (mapcar 'cadar items))))
          ;; 줄 간격 (원래 문자 간격 유지)
          (if (> (length rows) 1)
            (progn
              (setq ys (mapcar '(lambda (r) (cadr (car (car r)))) rows)
                    gap (/ (- (car ys) (last ys)) (1- (length ys)))
                    sp (max 0.25 (min 4.0 (/ gap (* h 1.6667)))))
            )
          )
          (if (al:make-mtext ed0 (al:v+ org (al:rot tl ang0)) content h ang0 sp)
            (progn
              (setq n 1)
              (if del (foreach e lst (entdel e)))
            )
          )
        )
      )
      (princ (strcat "\nMTEXT " (itoa n) "개 생성"))
    )
  )
  (al:end)
)

(defun al:mtext-angle (ed / d)
  (cond
    ((assoc 50 ed) (cdr (assoc 50 ed)))
    ((setq d (cdr (assoc 11 ed))) (angle '(0.0 0.0) (list (car d) (cadr d))))
    (T 0.0)
  )
)

;; MTEXT 하나를 TEXT 여러 개로. 만든 개수 반환
(defun al:mtext-to-texts (e / ed h ang att lines sp dist w hh col row tl i n p0)
  (setq ed (entget e)
        h (cdr (assoc 40 ed))
        ang (al:mtext-angle ed)
        att (cond ((cdr (assoc 71 ed))) (1))
        p0 (cdr (assoc 10 ed))
        lines (al:mt-paragraphs (al:mtext-string ed))
        sp (cond ((cdr (assoc 44 ed))) (1.0))
        dist (* h 1.6667 sp)
        w (cond ((cdr (assoc 42 ed))) (0.0))
        hh (cond ((cdr (assoc 43 ed))) ((+ h (* dist (1- (length lines))))))
        col (rem (1- att) 3)
        row (/ (1- att) 3)
        tl (list (- (* col w 0.5)) (* row hh 0.5))
        i 0 n 0)
  (foreach ln lines
    (if (/= (al:str-trim ln) "")
      (if (entmake (list '(0 . "TEXT") (assoc 8 ed)
                         (cons 10 (al:p3 (al:v+ p0 (al:rot (list (car tl) (- (cadr tl) h (* i dist))) ang))))
                         (cons 40 h) (cons 1 ln) (cons 50 ang) (assoc 7 ed)))
        (progn
          (setq n (1+ n))
          (if (assoc 62 ed) (entmod (append (entget (entlast)) (list (assoc 62 ed)))))
        )
      )
    )
    (setq i (1+ i))
  )
  n
)

(defun c:ALM2T (/ ss del n k)
  (al:begin)
  (princ "\nTEXT 로 바꿀 MTEXT 선택: ")
  (if (setq ss (ssget '((0 . "MTEXT"))))
    (progn
      (setq del (al:yes-p "\n원본 MTEXT 를 삭제할까요" "Yes") n 0)
      (foreach e (al:ss->list ss)
        (setq k (al:mtext-to-texts e) n (+ n k))
        (if (and del (> k 0)) (entdel e))
      )
      (princ (strcat "\nTEXT " (itoa n) "개 생성"))
    )
  )
  (al:end)
)

(defun c:ALMCLEAN (/ ss n ed s)
  (al:begin)
  (princ "\n서식을 지울 MTEXT 선택: ")
  (if (setq ss (ssget '((0 . "MTEXT"))))
    (progn
      (setq n 0)
      (foreach e (al:ss->list ss)
        (setq ed (entget e)
              s (al:str-join (mapcar 'al:mt-escape (al:mt-paragraphs (al:mtext-string ed))) "\\P"))
        (if (and (/= s (al:mtext-string ed)) (al:ent-text-set ed s)) (setq n (1+ n)))
      )
      (princ (strcat "\nMTEXT " (itoa n) "개 서식 제거"))
    )
  )
  (al:end)
)
