;;; ------------------------------------------------------------------
;;; AL_Find.lsp - 문자 찾기 / 바꾸기
;;;   -ALFIND : (명령행 버전) 문자 찾아 하나씩 확대해 보기, 찾은 객체 모두 선택
;;;   -ALFR   : (명령행 버전) 문자 찾아 바꾸기
;;;   대화상자 버전(ALFTE/ALFIND/ALFR)은 AL_FTE.lsp
;;; ------------------------------------------------------------------

(setq al:*text-types* "TEXT,MTEXT,INSERT,DIMENSION,MULTILEADER,ATTDEF")

;; 객체(속성 포함)의 문자 목록
(defun al:ent-strings (e / ed typ a out s)
  (setq ed (entget e) typ (cdr (assoc 0 ed)))
  (cond
    ((= typ "MTEXT") (list (al:mt-plain (al:mtext-string ed))))
    ((member typ '("TEXT" "ATTRIB" "ATTDEF" "DIMENSION")) (list (cdr (assoc 1 ed))))
    ((= typ "INSERT")
     (if (= (cdr (assoc 66 ed)) 1)
       (progn
         (setq a (entnext e))
         (while (and a (= (cdr (assoc 0 (entget a))) "ATTRIB"))
           (setq out (cons (cdr (assoc 1 (entget a))) out) a (entnext a))
         )
       )
     )
     out)
    ((and (= typ "MULTILEADER") (al:activex-p))
     (if (setq s (al:catch 'vla-get-TextString (list (vlax-ename->vla-object e))))
       (list (al:mt-plain s))
     ))
  )
)

(defun al:ent-contains-p (e str cs)
  (if (not cs) (setq str (strcase str)))
  (vl-some '(lambda (s) (and s (vl-string-search str (if cs s (strcase s)))))
           (al:ent-strings e))
)

;; 객체 하나에서 바꾸기. 바꾼 개수 반환. 잠긴 레이어 등으로 실패하면 al:*fail* 증가
(defun al:replace-in-ent (e old new cs / ed typ s r n a o)
  (setq ed (entget e) typ (cdr (assoc 0 ed)) n 0)
  (cond
    ((member typ '("TEXT" "MTEXT" "ATTRIB" "ATTDEF" "DIMENSION"))
     (setq s (al:ent-text ed))
     (if (and s (/= s ""))
       (progn
         (setq r (al:str-replace s old new cs (= typ "MTEXT")))
         (if (> (cadr r) 0)
           (if (al:ent-text-set ed (car r))
             (setq n (cadr r))
             (setq al:*fail* (1+ al:*fail*))
           )
         )
       )
     ))
    ((= typ "INSERT")
     (if (= (cdr (assoc 66 ed)) 1)
       (progn
         (setq a (entnext e))
         (while (and a (= (cdr (assoc 0 (entget a))) "ATTRIB"))
           (setq n (+ n (al:replace-in-ent a old new cs)) a (entnext a))
         )
         (if (> n 0) (entupd e))
       )
     ))
    ((and (= typ "MULTILEADER") (al:activex-p))
     (setq o (vlax-ename->vla-object e)
           s (al:catch 'vla-get-TextString (list o)))
     (if (and s (/= s ""))
       (progn
         (setq r (al:str-replace s old new cs T))
         (if (> (cadr r) 0)
           (if (vl-catch-all-error-p (vl-catch-all-apply 'vla-put-TextString (list o (car r))))
             (setq al:*fail* (1+ al:*fail*))
             (setq n (cadr r))
           )
         )
       )
     ))
  )
  n
)

;; 블록 정의 내부 (외부참조, 익명 블록 제외)
(defun al:replace-in-blockdefs (old new cs / b e n)
  (setq n 0 b (tblnext "BLOCK" T))
  (while b
    (if (and (/= (substr (cdr (assoc 2 b)) 1 1) "*")
             (= 0 (logand 36 (cdr (assoc 70 b)))))
      (progn
        (setq e (cdr (assoc -2 b)))
        (while e
          (setq n (+ n (al:replace-in-ent e old new cs)) e (entnext e))
        )
      )
    )
    (setq b (tblnext "BLOCK"))
  )
  n
)

(defun c:-ALFR (/ old new cs scope inblk ss total nb)
  (al:begin)
  (setq old (getstring T "\n찾을 문자: "))
  (if (= old "")
    (princ "\n찾을 문자가 없습니다.")
    (progn
      (setq new (getstring T (strcat "\n\"" old "\" 을(를) 바꿀 문자 (Enter=삭제): ")))
      (setq cs (al:yes-p "\n대소문자 구분" "No"))
      (setq scope (al:kword "\n범위 - 도면 전체(A)/선택(S) [All/Select] <Select>: " "All Select" "Select"))
      (if (= scope "All")
        (setq ss (ssget "X" (list (cons 0 al:*text-types*)))
              inblk (al:yes-p "\n블록 정의 내부 문자도 바꿀까요" "No"))
        (setq ss (ssget (list (cons 0 al:*text-types*))))
      )
      (setq total 0 nb 0 al:*fail* 0)
      (foreach e (al:ss->list ss)
        (setq total (+ total (al:replace-in-ent e old new cs)))
      )
      (if inblk
        (progn
          (setq nb (al:replace-in-blockdefs old new cs))
          (if (> nb 0) (command "_.REGEN"))
        )
      )
      (princ (strcat "\n바꾸기 완료: " (itoa (+ total nb)) "곳"
                     (if (> nb 0) (strcat " (블록 정의 내부 " (itoa nb) "곳 포함)") "")))
      (if (> al:*fail* 0)
        (princ (strcat "\n잠긴 레이어 등으로 바꾸지 못한 객체: " (itoa al:*fail*) "개"))
      )
    )
  )
  (al:end)
)

(defun al:zoom-to (e / bb pt ht ed)
  (if (setq bb (al:bbox e))
    (setq pt (al:mid (car bb) (cadr bb))
          ht (max (* 6.0 (- (cadr (cadr bb)) (cadr (car bb))))
                  (* 1.5 (- (car (cadr bb)) (car (car bb))))))
    (setq ed (entget e)
          pt (cdr (assoc 10 ed))
          ht (* 10.0 (cond ((cdr (assoc 40 ed))) (1.0))))
  )
  (if (> ht 0.0) (command "_.ZOOM" "_C" (al:p3 pt) ht))
)

(defun c:-ALFIND (/ str cs ss found n i k e)
  (al:begin)
  (setq str (getstring T "\n찾을 문자: "))
  (if (= str "")
    (princ "\n찾을 문자가 없습니다.")
    (progn
      (setq cs (al:yes-p "\n대소문자 구분" "No"))
      (setq ss (ssget "X" (list (cons 0 al:*text-types*) (cons 410 (getvar "CTAB")))))
      (foreach e (al:ss->list ss)
        (if (al:ent-contains-p e str cs) (setq found (cons e found)))
      )
      (setq found (reverse found) n (length found))
      (if (= n 0)
        (princ "\n현재 공간에서 찾은 문자가 없습니다.")
        (progn
          (princ (strcat "\n" (itoa n) "개 찾음."))
          (setq i 0 k "Next")
          (while (and (< i n) (/= k "Exit"))
            (setq e (nth i found))
            (al:zoom-to e)
            (redraw e 3)
            (initget "Next Prev Exit")
            (setq k (getkword (strcat "\n[" (itoa (1+ i)) "/" (itoa n) "] 다음(N)/이전(P)/끝내기(E) [Next/Prev/Exit] <Next>: ")))
            (redraw e 4)
            (cond
              ((= k "Prev") (setq i (max 0 (1- i))))
              ((= k "Exit"))
              (T (setq i (1+ i)))
            )
          )
          (princ (strcat "\n찾은 객체 " (itoa n) "개를 선택해 두었습니다."))
        )
      )
    )
  )
  (al:end)
  (if found (sssetfirst nil (al:list->ss found)))
  (princ)
)
